-- Sourced from ANSI X9.62 (1998)

ANSI-X9-62 { iso(1) member-body(2) us(840) 10045 module(4) 1 }
DEFINITIONS EXPLICIT TAGS ::= BEGIN
-- EXPORTS All;
-- IMPORTS None;

ansi-X9-62 OBJECT IDENTIFIER ::= { iso(1) member-body(2) us(840) 10045 }

FieldID { FIELD-ID:IOSet } ::= SEQUENCE { -- Finite field
    fieldType   FIELD-ID.&id({IOSet}),
    parameters  FIELD-ID.&Type({IOSet}{@fieldType})
}

FieldTypes FIELD-ID ::= {
    { Prime-p IDENTIFIED BY prime-field } |
    { Characteristic-two IDENTIFIED BY characteristic-two-field },
    ...
}

FIELD-ID ::= TYPE-IDENTIFIER -- ISO/IEC 8824-2:1995(E), Annex A
id-fieldType OBJECT IDENTIFIER ::= { ansi-X9-62 fieldType(1) }
prime-field OBJECT IDENTIFIER ::= { id-fieldType 1 }
characteristic-two-field OBJECT IDENTIFIER ::= { id-fieldType 2 }
Prime-p ::= INTEGER -- Finite field F(p), where p is an odd prime

Characteristic-two ::= SEQUENCE {
    m           INTEGER, -- Field size 2^m
    basis       CHARACTERISTIC-TWO.&id({BasisTypes}),
    parameters  CHARACTERISTIC-TWO.&Type({BasisTypes}{@basis})
}

BasisTypes CHARACTERISTIC-TWO::= {
    { NULL IDENTIFIED BY gnBasis } |
    { Trinomial IDENTIFIED BY tpBasis } |
    { Pentanomial IDENTIFIED BY ppBasis },
    ...
}

-- Trinomial basis representation of F2^m
-- Integer k for reduction polynomial xm + xk + 1

Trinomial ::= INTEGER

Pentanomial ::= SEQUENCE {
    --
    -- Pentanomial basis representation of F2^m
    -- reduction polynomial integers k1, k2, k3
    -- f(x) = x**m + x**k3 + x**k2 + x**k1 + 1
    --
    k1      INTEGER,
    k2      INTEGER,
    k3      INTEGER
}

CHARACTERISTIC-TWO ::= TYPE-IDENTIFIER

id-characteristic-two-basis OBJECT IDENTIFIER ::= { characteristic-two-field basisType(3) }
-- The object identifiers gnBasis, tpBasis and ppBasis name
-- three kinds of basis for characteristic-two finite fields
gnBasis OBJECT IDENTIFIER ::= { id-characteristic-two-basis 1 }
tpBasis OBJECT IDENTIFIER ::= { id-characteristic-two-basis 2 }
ppBasis OBJECT IDENTIFIER ::= { id-characteristic-two-basis 3 }

FieldElement ::= OCTET STRING -- Finite field element
ECPoint ::= OCTET STRING -- Elliptic curve point

ECParameters ::= SEQUENCE { -- Elliptic curve parameters
    version         INTEGER { ecpVerl(1) } (ecpVerl),
    fieldID         FieldID {{FieldTypes}},
    curve           Curve,
    base            ECPoint, -- Base point G
    order           INTEGER, -- Order n of the base point
    cofactor        INTEGER OPTIONAL, -- The integer h = #E(Fq)/n
    ...
}

Curve ::= SEQUENCE {
    a       FieldElement, -- Elliptic curve coefficient a
    b       FieldElement, -- Elliptic curve coefficient b
    seed    BIT STRING OPTIONAL
}

ECDSA-Sig-Value ::= SEQUENCE {
    r       INTEGER,
    s       INTEGER
}

id-ecSigType OBJECT IDENTIFIER ::= { ansi-X9-62 signatures(4) }

ecdsa-with-SHA1 OBJECT IDENTIFIER ::= { id-ecSigType 1 }

SubjectPublicKeylnfo ::= SEQUENCE {
    algorithm           Algorithmldentifier {{ECPKAlgorithms}},
    subjectPublicKey    BIT STRING
}

Algorithmldentifier { ALGORITHM:IOSet } ::= SEQUENCE {
    algorithm       ALGORITHM.&id({IOSet}),
    parameters      ALGORITHM.&Type({IOSet}{@algorithm})
}

ECPKAlgorithms ALGORITHM ::= {
    ecPublicKeyType,
    ...
}

ecPublicKeyType ALGORITHM ::= {
    Parameters IDENTIFIED BY id-ecPublicKey
}

ALGORITHM ::= TYPE-IDENTIFIER
id-publicKeyType OBJECT IDENTIFIER ::= { ansi-X9-62 keyType(2) }
id-ecPublicKey OBJECT IDENTIFIER ::= { id-publicKeyType 1 }

Parameters ::= CHOICE {
    ecParameters        ECParameters,
    namedCurve          CURVES.&id({CurveNames}),
    implicitlyCA        NULL
}

CurveNames CURVES ::= {
    { ID c2pnb163v1 } | -- J.4.1, example 1 --
    { ID c2pnb163v2 } | -- J.4.1, example 2 --
    { ID c2pnb163v3 } | -- J.4.1, example 3 --
    { ID c2pnb176w1 } | -- J.4.2, example 1 --
    { ID c2tnb191v1 } | -- J.4.3, example 1 --
    { ID c2tnb191v2 } | -- J.4.3, example 2 --
    { ID c2tnb191v3 } | -- J.4.3, example 3 --
    { ID c2onb191v4 } | -- J.4.3, example 4 --
    { ID c2onb191v5 } | -- J.4.3, example 5 --
    { ID c2pnb208w1 } | -- J.4.4, example 1 --
    { ID c2tnb239v1 } | -- J.4.5, example 1 --
    { ID c2tnb239v2 } | -- J.4.5, example 2 --
    { ID c2tnb239v3 } | -- J.4.5, example 3 --
    { ID c2onb239v4 } | -- J.4.5, example 4 --
    { ID c2onb239v5 } | -- J.4.5, example 5 --
    { ID c2pnb272w1 } | -- J.4.6, example 1 --
    { ID c2pnb304w1 } | -- J.4.7, example 1 --
    { ID c2tnb359v1 } | -- J.4.8, example 1 --
    { ID c2pnb368w1 } | -- J.4.9, example 1 --
    { ID c2tnb431r1 } | -- J.4.10, example 1 --
    { ID prime192v1 } | -- J.5.1, example 1 --
    { ID prime192v2 } | -- J.5.1, example 2 --
    { ID prime192v3 } | -- J.5.1, example 3 --
    { ID prime239v1 } | -- J.5.2, example 1 --
    { ID prime239v2 } | -- J.5.2, example 2 --
    { ID prime239v3 } | -- J.5.2, example 3 --
    { ID prime256v1 },  -- J.5.3, example 1 --
    ... -- others --
}

CURVES ::= CLASS {
    &id OBJECT IDENTIFIER UNIQUE
}
WITH SYNTAX { ID &id }

ellipticCurve OBJECT IDENTIFIER ::= { ansi-X9-62 curves(3) }

c-TwoCurve OBJECT IDENTIFIER ::= { ellipticCurve characteristicTwo(0) }

primeCurve OBJECT IDENTIFIER ::= { ellipticCurve prime(1) }

c2pnb163v1 OBJECT IDENTIFIER ::= { c-TwoCurve 1 }
c2pnb163v2 OBJECT IDENTIFIER ::= { c-TwoCurve 2 }
c2pnb163v3 OBJECT IDENTIFIER ::= { c-TwoCurve 3 }
c2pnb176w1 OBJECT IDENTIFIER ::= { c-TwoCurve 4 }
c2tnb191v1 OBJECT IDENTIFIER ::= { c-TwoCurve 5 }
c2tnb191v2 OBJECT IDENTIFIER ::= { c-TwoCurve 6 }
c2tnbl91v3 OBJECT IDENTIFIER ::= { c-TwoCurve 7 }
c2onb191v4 OBJECT IDENTIFIER ::= { c-TwoCurve 8 }
c2onb191v5 OBJECT IDENTIFIER ::= { c-TwoCurve 9 }
c2pnb208w1 OBJECT IDENTIFIER ::= { c-TwoCurve 10 }
c2tnb239v1 OBJECT IDENTIFIER ::= { c-TwoCurve 11 }
c2tnb239v2 OBJECT IDENTIFIER ::= { c-TwoCurve 12 }
c2tnb239v3 OBJECT IDENTIFIER ::= { c-TwoCurve 13 }
c2onb239v4 OBJECT IDENTIFIER ::= { c-TwoCurve 14 }
c2onb239v5 OBJECT IDENTIFIER ::= { c-TwoCurve 15 }
c2pnb272w1 OBJECT IDENTIFIER ::= { c-TwoCurve 16 }
c2pnb304w1 OBJECT IDENTIFIER ::= { c-TwoCurve 17 }
c2tnb359v1 OBJECT IDENTIFIER ::= { c-TwoCurve 18 }
c2pnb368w1 OBJECT IDENTIFIER ::= { c-TwoCurve 19 }
c2tnb431r1 OBJECT IDENTIFIER ::= { c-TwoCurve 20 }
prime192v1 OBJECT IDENTIFIER ::= { primeCurve 1 }
prime192v2 OBJECT IDENTIFIER ::= { primeCurve 2 }
prime192v3 OBJECT IDENTIFIER ::= { primeCurve 3 }
prime239v1 OBJECT IDENTIFIER ::= { primeCurve 4 }
prime239v2 OBJECT IDENTIFIER ::= { primeCurve 5 }
prime239v3 OBJECT IDENTIFIER ::= { primeCurve 6 }
prime256v1 OBJECT IDENTIFIER ::= { primeCurve 7 }

END
